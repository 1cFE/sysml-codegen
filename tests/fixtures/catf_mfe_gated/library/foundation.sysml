// Foundation Package for Fusion Modeling
// Phase 0: Basic structure and top-level definitions

package Fusion {
    doc /*
    Root package for fusion energy system modeling.

    This package provides the foundation for:
    - Component libraries (reusable definitions)
    - Specific designs (instances)
    - Analysis studies (parametric evaluations)

    **Version**: Phase 0
    **Status**: Foundation
    */

    public import ScalarValues::*;
    public import SI::*;
    public import ISQ::*;
}
