package ns {
    private import ScalarValues::*;
    private import NumericalFunctions::sum;
    part def Server { attribute power : Real default 10.0; }
    part servers : Server[2];
    part server_1 : Server :> servers { :>> power = 15.0; }
    attribute total : Real = sum(servers.power);
}
