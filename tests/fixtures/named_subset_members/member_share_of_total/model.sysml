package ns {
    private import ScalarValues::*;
    private import NumericalFunctions::sum;
    part def Server { attribute power : Real default 10.0; }
    part def Rack { part servers : Server[2]; attribute total : Real = sum(servers.power); }
    part def Hall { part racks : Rack[2]; attribute total : Real = sum(racks.total); }
    part hall : Hall {
        part rack_1 :> racks { attribute share : Real = total / sum(racks.total); }
    }
}
