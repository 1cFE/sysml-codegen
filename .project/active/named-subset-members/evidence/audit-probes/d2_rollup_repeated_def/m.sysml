package s {
    private import ScalarValues::*;
    private import NumericalFunctions::sum;
    part def Server { attribute power : Real default 10.0; }
    part def Rack { part servers : Server[2]; part server_1 :> servers { :>> power = 15.0; } attribute total : Real = sum(servers.power); }
    part def Hall { part racks : Rack[2]; part rack_1 :> racks; attribute total : Real = sum(racks.total); }
    part def Site { part halls : Hall[2]; attribute total : Real = sum(halls.total); }
    part site : Site { part hall_1 :> halls; }
}
